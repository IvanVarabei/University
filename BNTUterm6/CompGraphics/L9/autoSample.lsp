(command "_rectang" "0,0" "@100,60")
(command "_extrude" "_last" "" "25")
(setq Body1 (entlast))
(command "_rectang" "20,-2" "@60,12")
(command "_extrude" "_last" "" "30")
(setq Body2 (entlast))
(command "_rectang" "0,35" "@100,25")
(command "_extrude" "_last" "" "75")
(setq Body3 (entlast))
(command "_ucs" "_3" "50,35,75" "100,35,75" "0,35,100")
(command "_circle"  "0,0,0" "35")
(command "_extrude" "_last" "" "-25")
(setq Body4 (entlast))
(command "_circle"  "0,0,0" "20")
(command "_extrude" "_last" "" "-25")
(setq Body5 (entlast))
(command "_subtract" Body1 "" Body2 "")
(command "_subtract" Body3 Body4 "" Body5 "")
(command "_union" Body1 Body3 Body4 "")
(command "_ucs" "_w")
(command "_-view" "_swiso")
